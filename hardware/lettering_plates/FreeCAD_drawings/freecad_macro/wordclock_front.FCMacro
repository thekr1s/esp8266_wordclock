import FreeCAD, Draft

import os
import sys
work_dir = os.path.split(os.path.abspath(os.getcwd()))[0]
sys.path.append(work_dir)

import LightDivider
import FrontPlate
from LetterPlateText import *

GENERATE_RIBBA_13_13 = False
GENERATE_RIBBA_13_13_V2 = True
GENERATE_RIBBA_11_11 = False

INSERT_FRONT_PLATE = True
INSERT_SCOTS = False
INSERT_SCOTS_BIG = False

########################################################
########################################################
if GENERATE_RIBBA_13_13 or GENERATE_RIBBA_13_13_V2:
	FONT = "C:/tmp/FreeCAD macros/fonts/LiberationMono-Regular-stencil.ttf"
	FONT_SCALE = 0.90
	LED_OFFSET = 1000.0/30.0	#1 meter / 30 leds
	FRONT_PLATE_SIZE = 500.0
	LDR_DIAMETER = 5.12	
	SCOTS_DEPTH = 12.0
	SCOTS_MATERIAL_THICKNESS = 5.0
	if GENERATE_RIBBA_13_13:
		FRONT_PLATE_SIZE = 500.0
		FONT = "C:/tmp/FreeCAD macros/fonts/LiberationMono-Regular-stencil.ttf"
		WORDCLOCK_TEXT = WORDCLOCK_TEXT_13_13
	if GENERATE_RIBBA_13_13_V2:
		FONT = "C:/tmp/FreeCAD macros/fonts/LiberationMono-V2.ttf"
		FRONT_PLATE_SIZE = 550.0
		WORDCLOCK_TEXT = WORDCLOCK_TEXT_13_13_V2
	NUMBER_OF_LEDS = len(WORDCLOCK_TEXT[0]) #TODO we expect a even X and Y nr of leds

########################################################
########################################################
if GENERATE_RIBBA_11_11:
	FONT = "C:/Users/Rutger/Dropbox/Hobby/wordclock_git/hardware/lettering_plates/fonts/LiberationMono-Regular-stencil.ttf"
	FONT_SCALE = 0.98
	LED_OFFSET = 1000.0/60.0	#1 meter / 60 leds
	FRONT_PLATE_SIZE = 230.0
	LDR_DIAMETER = 5.12	
	SCOTS_DEPTH = 12.0
	SCOTS_MATERIAL_THICKNESS = 5.0
	WORDCLOCK_TEXT = WORDCLOCK_TEXT_11_11
	NUMBER_OF_LEDS = len(WORDCLOCK_TEXT[0])


#WORDCLOCK_TEXT = ["HETABDOPRJI"] #Handy for debugging faster generation!

########################################################
########################################################
if INSERT_FRONT_PLATE:
	part = App.activeDocument().addObject('App::Part','Part')
	front_plate_lib = FrontPlate.front_plate( part, WORDCLOCK_TEXT, FONT, FONT_SCALE, LED_OFFSET, FRONT_PLATE_SIZE, FRONT_PLATE_SIZE, LDR_DIAMETER, SCOTS_MATERIAL_THICKNESS)
#	Handy for debugging this way the underlying light divider is also drawn
#	front_plate_lib.change_draw_settings(drawText = True, drawSquares = True, drawSquaresHoles = True, drawLdr = True, drawOutline = True)
	front_plate = front_plate_lib.create()

########################################################
########################################################
if INSERT_SCOTS:
	part1 = App.activeDocument().addObject('App::Part','Part')
	lightDividerLength = NUMBER_OF_LEDS*LED_OFFSET + SCOTS_WIDTH - LASER_CUTTING_WIDTH
	small_light_divider= LightDivider.light_divider(part1, SCOTS_DEPTH, lightDividerLength, SCOTS_MATERIAL_THICKNESS, NUMBER_OF_LEDS, LED_OFFSET).create()
	
	#we need Horizontaal and vertical scots and for both a closing one
	for i in range(2*(NUMBER_OF_LEDS+1)):
		new_scot = App.ActiveDocument.copyObject(small_light_divider, False)
		new_scot.Placement.Base = FreeCAD.Vector(i*(SCOTS_DEPTH+OBJECT_CLEARANCE), 0, 0)
		part1.addObject(new_scot)

########################################################
########################################################
if INSERT_SCOTS_BIG:
	part2 = App.activeDocument().addObject('App::Part','Part')
	big_light_divider = LightDivider.light_divider(part2, SCOTS_DEPTH, FRONT_PLATE_SIZE, SCOTS_MATERIAL_THICKNESS, NUMBER_OF_LEDS, LED_OFFSET).create()
	
	for i in range(4+2):
		new_scot = App.ActiveDocument.copyObject(big_light_divider, False)
		new_scot.Placement.Base = FreeCAD.Vector(i*(SCOTS_DEPTH+OBJECT_CLEARANCE), 0, 0)
		part2.addObject(new_scot)
