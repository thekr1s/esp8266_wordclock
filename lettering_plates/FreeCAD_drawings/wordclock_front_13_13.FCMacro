import FreeCAD, Draft

try:
	from freecad_macro_libs import LightDivider
	from freecad_macro_libs import FrontPlate
except:
	import LightDivider
	import FrontPlate

# For the 13X13 wordclock we use the {product key) with 30 led on a meter.
# This result in a distens between the leds of 100/30=3.333cm
# For a wordclock of 13x13 we need a frame of 13x3.3 + spacing this result in 45 cm 
# I want the front plate to overlap the rear panal, so the front plant needs to be at least 49cm

FONT = "C:/Users/Rutger/Dropbox/Hobby/wordclock_git/lettering_plates/fonts/LiberationMono-Regular-stencil-50cm.ttf"
FONT_SCALE = 0.98

INSERT_FRONT_PLATE = True
INSERT_SCOTS = False
INSERT_SCOTS_BIG = False

LED_OFFSET = 1000.0/30.0	#1 meter / 30 leds
FRONT_PLATE_SIZE = 500.0
#FRONT_PLATE_SIZE = 490.0

LDR_DIAMETER = 5.0	

SCOTS_DEPTH = 15.0
SCOTS_MATERIAL_THICKNESS = 5.0 #materiaal dikte

WORDCLOCK_TEXT = ["HETGISENUZELF",
"BIJNAWDERTIEN",
"DRIENEGENTIEN",
"ZEVENTIENVIJF",
"TWEENVIERTIEN",
"ACHTTIENKWART",
"ZESTIENTWAALF",
"OVERVOOROHALF",
"VIJFWACHTDRIE",
"TWEENZESZEVEN",
"TIENTWAALFELF",
"BVIERNEGENRWA",
"VUURAGEWEESTU"]
#WORDCLOCK_TEXT = ["HETABDOPRJIEL"]
NUMBER_OF_LEDS = len(WORDCLOCK_TEXT[0])

########################################################
########################################################
if INSERT_FRONT_PLATE:
	part = App.activeDocument().addObject('App::Part','Part')
	front_plate_lib = FrontPlate.front_plate( part, WORDCLOCK_TEXT, FONT, FONT_SCALE, LED_OFFSET, FRONT_PLATE_SIZE, FRONT_PLATE_SIZE, LDR_DIAMETER, SCOTS_MATERIAL_THICKNESS)
#	front_plate_lib.change_draw_settings(drawText = True, drawSquares = True, drawSquaresHoles = True, drawLdr = True, drawOutline = True)
	front_plate = front_plate_lib.create()


########################################################
########################################################
if INSERT_SCOTS:
	part1 = App.activeDocument().addObject('App::Part','Part')
	lightDividerLength = NUMBER_OF_LEDS*LED_OFFSET + SCOTS_WIDTH - LASER_CUTTING_WIDTH
	small_light_divider= LightDivider.light_divider(part1, SCOTS_DEPTH, lightDividerLength, SCOTS_MATERIAL_THICKNESS, NUMBER_OF_LEDS, LED_OFFSET).create()
	
	#we need Horizontaal and vertical scots and for both a closing one
	for i in range(2*(NUMBER_OF_LEDS+1)):
		new_scot = App.ActiveDocument.copyObject(small_light_divider, False)
		new_scot.Placement.Base = FreeCAD.Vector(i*(SCOTS_DEPTH+OBJECT_CLEARANCE), 0, 0)
		part1.addObject(new_scot)

########################################################
########################################################
if INSERT_SCOTS_BIG:
	part2 = App.activeDocument().addObject('App::Part','Part')
	big_light_divider = LightDivider.light_divider(part2, SCOTS_DEPTH, FRONT_PLATE_SIZE, SCOTS_MATERIAL_THICKNESS, NUMBER_OF_LEDS, LED_OFFSET).create()
	
	for i in range(4+2):
		new_scot = App.ActiveDocument.copyObject(big_light_divider, False)
		new_scot.Placement.Base = FreeCAD.Vector(i*(SCOTS_DEPTH+OBJECT_CLEARANCE), 0, 0)
		part2.addObject(new_scot)
